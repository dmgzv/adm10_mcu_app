module ipg-fcs {
  yang-version 1;
  namespace "http://www.ipg.com/horizon/fcs";
  prefix ipg-fcs;

  import ipg-common {
    prefix "ipg-cmn";
    revision-date "2019-08-10";
  }

  import ipg-system {
    prefix "ipg-sys";
    revision-date "2019-08-10";
  }

  organization "IPG";
  contact "IPG";
  description "This module describes fan card slots";
  revision "2019-11-20" {
    description "Initial revision of fan cards slots schema";
    reference "";
  }

  augment /ipg-sys:system {
    description "Augment of /system with fan card slots";

    list fan-card-slot {
      description "Fan card slot";
      key "id";
      max-elements 3;
      leaf id {
        description "Slot ID";
        type uint32 {
          range "1..3";
        }
      }
      leaf admin-state {
        description "Administrative state";
        ipg-cmn:category "config";
        type ipg-cmn:admin-state-type-IS;
        default IS;
        config true;
      }
      leaf service-state {
        description "Service state";
        ipg-cmn:category "monitor";
        ipg-cmn:condition;
        type ipg-cmn:service-state-type-UEQ-IS;
        config false;
      }
      leaf card-module-name {
        when "../admin-state != 'DSBLD'";
        description "Card module name";
        ipg-cmn:category "inventory";
        type ipg-cmn:string-64;
        config false;
        default "ipg-fb-k10@2019-11-27";        // This default added for generating data model
      }
    }
  }
}
