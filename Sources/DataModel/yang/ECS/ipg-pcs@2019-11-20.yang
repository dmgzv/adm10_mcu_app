module ipg-pcs {
  yang-version 1;
  namespace "http://www.ipg.com/horizon/pcs";
  prefix ipg-pcs;

  import ipg-common {
    prefix "ipg-cmn";
    revision-date "2019-08-10";
  }

  import ipg-system {
    prefix "ipg-sys";
    revision-date "2019-08-10";
  }

  organization "IPG";
  contact "IPG";
  description "This module describes power card slots";
  revision "2019-11-20" {
    description "Initial revision of power cards slots schema";
    reference "";
  }

  augment /ipg-sys:system {
    description "Augment of /system with power card slots";

    list power-card-slot {
      description "Power card slot";
      key "id";
      max-elements 2;
      leaf id {
        description "Slot ID";
        type uint32 {
          range "1..2";
        }
      }
      leaf admin-state {
        description "Administrative state";
        ipg-cmn:category "config";
        type ipg-cmn:admin-state-type-IS;
        default IS;
        config true;
      }
      leaf service-state {
        description "Service state";
        ipg-cmn:category "monitor";
        ipg-cmn:condition;
        type ipg-cmn:service-state-type-UEQ-IS;
        config false;
      }
      leaf card-module-name {
        when "../admin-state != 'DSBLD'";
        description "Card module name";
        ipg-cmn:category "inventory";
        type ipg-cmn:string-64;
        config false;
        default "ipg-pem-h3@2019-11-29";        // This default added for generating data model
      }
    }
  }
}
